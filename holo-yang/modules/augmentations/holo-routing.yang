module holo-routing {
  yang-version 1.1;
  namespace "http://holo-routing.org/yang/holo-routing";
  prefix holo-routing;

  import ietf-inet-types {
    prefix "inet";
    reference "RFC 6991: Common YANG Data Types";
  }

  import ietf-yang-types {
    prefix "yang";
    reference "RFC 6991: Common YANG Data Types";
  }

  import ietf-routing {
    prefix "rt";
  }

  import ietf-bier {
    prefix "bier";
  }

  organization
    "Holo Routing Stack";

  description
    "This module defines augment statements for the ietf-routing
    module.";

  augment "/rt:routing" {
    container fib {
      config false;
      description
        "Kernel FIB install gate and high-performance counters.
         Queried via northbound GetState (gRPC/gNMI). Counters use
         atomic increments on the RIB update path.";

      leaf install-enabled {
        type boolean;
        description
          "True when holod.toml [routing].fib_install is enabled and
           netlink RouteAdd/RouteDel are performed. False means
           control-plane-only mode (in-process RIB still updates).";
      }

      leaf ip-installs {
        type yang:counter64;
        description "IP routes enqueued for netlink RouteAdd.";
      }
      leaf ip-installs-skipped {
        type yang:counter64;
        description "IP installs skipped because fib-install is false.";
      }
      leaf ip-uninstalls {
        type yang:counter64;
        description "IP routes enqueued for netlink RouteDel.";
      }
      leaf ip-uninstalls-skipped {
        type yang:counter64;
        description "IP uninstalls skipped because fib-install is false.";
      }
      leaf mpls-installs {
        type yang:counter64;
        description "MPLS routes enqueued for netlink RouteAdd.";
      }
      leaf mpls-installs-skipped {
        type yang:counter64;
        description "MPLS installs skipped because fib-install is false.";
      }
      leaf mpls-uninstalls {
        type yang:counter64;
        description "MPLS routes enqueued for netlink RouteDel.";
      }
      leaf mpls-uninstalls-skipped {
        type yang:counter64;
        description "MPLS uninstalls skipped because fib-install is false.";
      }
      leaf rib-ipv4-active {
        type yang:counter64;
        description "Active IPv4 prefixes currently in the in-process RIB.";
      }
      leaf rib-ipv6-active {
        type yang:counter64;
        description "Active IPv6 prefixes currently in the in-process RIB.";
      }
      leaf rib-mpls-entries {
        type yang:counter64;
        description "MPLS label entries currently in the in-process RIB.";
      }
    }

    container birts {
      description "BIER routing tables";
      list birt {
        key "sub-domain-id";
        description "BIER Routing table";
        config false;
        leaf sub-domain-id {
          config false;
          type uint8;
          description "BIER sub-domain-id";
        }
        list bfr-id {
          key "bfr-id";
          config false;
          leaf bfr-id {
            config false;
            type uint16;
            description "BFR identifier";
          }
          list birt-entry {
            key "bsl";
            config false;
            leaf bsl {
              config false;
              // FIXME: should be bier:bsl but got some issues with yang-rs
              type uint8;
              description "Bitstring length associated with the current entry";
            }
            leaf bfr-prefix {
              config false;
              type inet:ip-address;
              description "BFR's prefix";
            }
            leaf bfr-nbr {
              config false;
              type inet:ip-address;
              description "Neighbor BFR prefix";
            }
          }
        }
      }
    }
  }
}
